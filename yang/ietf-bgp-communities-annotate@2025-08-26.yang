module ietf-bgp-communities-annotate {
  yang-version 1.1;
  namespace
    "urn:ietf:params:xml:ns:yang:ietf-bgp-communities-annotate";
  prefix bgp-comm-an;

  import ietf-bgp-communities {
    prefix bgp-comm;
    reference
      "draft-ietf-grow-yang-bgp-communities-06: A YANG Data
       Model for BGP Communities";
  }
  import ietf-routing {
    prefix rt;
    reference
      "RFC 8349: A YANG Data Model for Routing Management
       (NMDA Version).";
  }
  import ietf-bgp {
    prefix bgp;
    reference
      "draft-ietf-idr-bgp-model-18: YANG Model for Border
       Gateway Protocol (BGP-4)";
  }

  organization
    "IETF GROW Working Group";
  contact
    "WG Web:   <https://datatracker.ietf.org/wg/grow/>
     WG List:  <mailto:grow@ietf.org>

     Author:   Martin Pels
       <mailto:mpels@ripe.net>";
  description
    "This module augments the ietf-bgp module with support for
     community annotations.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC YYYY; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC-EDITOR: please update YYYY with this RFC ID

  revision 2025-08-26 {
    description
      "Initial revision.";
    reference
      "RFC YYYY: A YANG Data Model for BGP Communities
       RFC-EDITOR: please update YYYY with this RFC ID";
  }

  augment "/rt:routing/rt:control-plane-protocols/"
        + "rt:control-plane-protocol/bgp:bgp/bgp:rib/"
        + "bgp:communities/bgp:community" {
    description
      "Augments a Regular BGP community from the
       ietf-bgp module with an optional annotation.";
    container annotation {
      presence "true";
      description
        "The presence of this container indicates
         that a community definition is available";
      uses bgp-comm:regular-community;
    }
  }

  augment "/rt:routing/rt:control-plane-protocols/"
        + "rt:control-plane-protocol/bgp:bgp/bgp:rib/"
        + "bgp:ext-communities/bgp:ext-community" {
    description
      "Augments an Extended BGP community from the
       ietf-bgp module with an optional annotation.";
    container annotation {
      presence "true";
      description
        "The presence of this container indicates
         that a community definition is available";
      uses bgp-comm:extended-community;
    }
  }

  augment "/rt:routing/rt:control-plane-protocols/"
        + "rt:control-plane-protocol/bgp:bgp/bgp:rib/"
        + "bgp:large-communities/bgp:large-community" {
    description
      "Augments a Large BGP community from the
       ietf-bgp module with an optional annotation.";
    container annotation {
      presence "true";
      description
        "The presence of this container indicates
         that a community definition is available";
      uses bgp-comm:large-community;
    }
  }
}
